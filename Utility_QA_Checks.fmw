FME workspace Utility_QA_Checks.fmw

Parameters:
- SourceDataset_FILEGDB = C:\Users\mirza\Desktop\RESUMES AND COVER LETTERS\PROJECTS\Utility_Network_Asset_QA_and_QC_Pipeline\Utility_Network_Asset_QA_and_QC_Pipeline\Utility_Network_Asset_QA_and_QC_Pipeline.gdb   # File Geodatabase
- SourceDataset_FILEGDB_3 = C:\Users\mirza\Desktop\RESUMES AND COVER LETTERS\PROJECTS\Utility_Network_Asset_QA_and_QC_Pipeline\Utility_Network_Asset_QA_and_QC_Pipeline\Utility_Network_Asset_QA_and_QC_Pipeline.gdb   # File Geodatabase
- DestDataset_FILEGDB_12 = C:\Users\mirza\Desktop\RESUMES AND COVER LETTERS\PROJECTS\Utility_Network_Asset_QA_and_QC_Pipeline\Utility_Network_Asset_QA_and_QC_Pipeline\Utility_Network_Asset_QA_and_QC_Pipeline.gdb   # File Geodatabase
- DestDataset_FILEGDB_10 = C:\Users\mirza\Desktop\RESUMES AND COVER LETTERS\PROJECTS\Utility_Network_Asset_QA_and_QC_Pipeline\Utility_Network_Asset_QA_and_QC_Pipeline\Utility_Network_Asset_QA_and_QC_Pipeline.gdb   # File Geodatabase
- DestDataset_FILEGDB_9 = C:\Users\mirza\Desktop\RESUMES AND COVER LETTERS\PROJECTS\Utility_Network_Asset_QA_and_QC_Pipeline\Utility_Network_Asset_QA_and_QC_Pipeline\Utility_Network_Asset_QA_and_QC_Pipeline.gdb   # File Geodatabase
- DestDataset_FILEGDB_11 = C:\Users\mirza\Desktop\RESUMES AND COVER LETTERS\PROJECTS\Utility_Network_Asset_QA_and_QC_Pipeline\Utility_Network_Asset_QA_and_QC_Pipeline\Utility_Network_Asset_QA_and_QC_Pipeline.gdb   # File Geodatabase

Readers:
- FILEGDB_1: FILEGDB from $(SourceDataset_FILEGDB)
- FILEGDB_2: FILEGDB from $(SourceDataset_FILEGDB_3)

Writers:
- FILEGDB_5: FILEGDB to $(DestDataset_FILEGDB_12)
- FILEGDB_6: FILEGDB to $(DestDataset_FILEGDB_10)
- FILEGDB_7: FILEGDB to $(DestDataset_FILEGDB_9)
- FILEGDB_8: FILEGDB to $(DestDataset_FILEGDB_11)

Water_Valves_W13 (reader FILEGDB_2)
    attributes: OBJECTID objectid, _id1 double, Asset_I2 text(80), Water_V3 double, Water_V4 text(80), Water_V5 text(80)
    -> Tester_5
Tester_5
    BOOL_OP = OR
    TEST_CLAUSE:
      TEST Asset I2 ATTRIBUTE_IS_EMPTY ""
      TEST Water V3 = 0
      TEST Water V5 ATTRIBUTE_IS_EMPTY ""
    TEST_MODE = TEST
    PASSED -> AttributeCreator_6
    FAILED -> DuplicateFilter_2
AttributeCreator_6
    ATTR_TABLE:
      SET_TO ERROR_TYPE (varchar(14)) = NULL_ATTRIBUTE
      SET_TO ERROR_DESC (varchar(37)) = One or more critical fields are empty
      SET_TO SOURCE_FC (varchar(16)) = Water_Valves_W13
    -> AttributeRenamer
DuplicateFilter_2
    INPUT_ORDERED_CHOICE_LOOKUP = NO
    KEYATTR = Asset_I2
    INPUT_ORDERED_CHOICE = No
    UNIQUE -> Tester_6
    DUPLICATE -> AttributeCreator_7
Tester_6
    BOOL_OP = OR
    TEST_CLAUSE = TEST @Value(OBJECTID) = 0
    TEST_MODE = TEST
    PASSED -> AttributeCreator_8
    FAILED -> Tester_7
AttributeCreator_8
    ATTR_TABLE:
      SET_TO ERROR_TYPE (varchar(16)) = INVALID_DIAMETER
      SET_TO ERROR_DESC (varchar(22)) = Diameter value is zero
      SET_TO SOURCE_FC (varchar(16)) = Water_Valves_W13
    -> AttributeRenamer
Tester_7
    BOOL_OP = AND
    TEST_CLAUSE:
      TEST @Value(Water_V5) != Gate
      TEST @Value(Water_V5) != Butterfly
      TEST @Value(Water_V5) != Ball
      TEST @Value(Water_V5) != Check
    TEST_MODE = TEST
    PASSED -> AttributeCreator_9
    FAILED -> Tester_8
AttributeCreator_9
    ATTR_TABLE:
      SET_TO ERROR_TYPE (varchar(18)) = INVALID_VALVE_TYPE
      SET_TO ERROR_DESC (varchar(31)) = Valve type not in approved list
      SET_TO SOURCE_FC (varchar(16)) = Water_Valves_W13
    -> AttributeRenamer
Tester_8
    BOOL_OP = OR
    TEST_CLAUSE = TEST @Value(Water_V4) != DIST
    TEST_MODE = TEST
    PASSED -> AttributeCreator_10
    FAILED -> AttributeManager_4
AttributeCreator_10
    ATTR_TABLE:
      SET_TO ERROR_TYPE (varchar(20)) = INVALID_NETWORK_TYPE
      SET_TO ERROR_DESC (varchar(24)) = Network type is not DIST
      SET_TO SOURCE_FC (varchar(16)) = Water_Valves_W13
    -> AttributeRenamer
AttributeManager_4
    ATTR_TABLE:
      REMOVE OBJECTID (int32)
      REMOVE _id1 (real64)
      RENAME_SET_VALUE Asset_I2 > QA_ASSET_ID (varchar(80))
      REMOVE Water_V3 (real64)
      REMOVE Water_V4 (varchar(80))
      REMOVE Water_V5 (varchar(80))
      SET_TO QA_STATUS (varchar(4)) = PASS
    USER_EXPOSED_ATTRIBUTES = QA_STATUS
    -> Valves_QA_Passed (writer FILEGDB_8)
Valves_QA_Passed (writer FILEGDB_8)
    attributes: QA_ASSET_ID text(80), QA_STATUS text(4)
AttributeCreator_7
    ATTR_TABLE:
      SET_TO ERROR_TYPE (varchar(18)) = DUPLICATE_ASSET_ID
      SET_TO ERROR_DESC (varchar(31)) = Asset ID appears more than once
      SET_TO SOURCE_FC (varchar(16)) = Water_Valves_W13
    -> AttributeRenamer
AttributeRenamer
    ATTR_TABLE = RENAME_SET_DEFAULT Asset_I2 > QA_ASSET_ID
    KEEP_RENAMED_ONLY = no
    MISSING_INPUT_ATTRS = REMOVE
    -> AttributeManager_2
AttributeManager_2
    ATTR_TABLE:
      REMOVE OBJECTID (int32)
      REMOVE _id1 (real64)
      REMOVE Water_V3 (real64)
      REMOVE Water_V4 (varchar(80))
      REMOVE Water_V5 (varchar(80))
    USER_EXPOSED_ATTRIBUTES = Asset I2,ERROR_TYPE,ERROR_DESC,SOURCE_FC
    -> Valves_QA_Errors (writer FILEGDB_6)
Valves_QA_Errors (writer FILEGDB_6)
    attributes: ERROR_TYPE text(18), ERROR_DESC text(31), SOURCE_FC text(16), QA_ASSET_ID text(80)
Water_Mains_W13 (reader FILEGDB_1)
    attributes: OBJECTID objectid, _id1 double, Waterma2 text(80), Waterma3 text(80), Waterma4 double, Waterma5 text(80), Waterma6 text(80), Waterma7 double, Waterma8 double, Waterma9 text(80), Shape_Length double
    -> Tester
Tester
    BOOL_OP = OR
    TEST_CLAUSE:
      TEST Waterma2 ATTRIBUTE_IS_EMPTY ""
      TEST @Value(Waterma4) = 0
      TEST Waterma5 ATTRIBUTE_IS_EMPTY ""
      TEST @Value(Waterma7) = 0
    TEST_MODE = TEST
    PASSED -> AttributeCreator
    FAILED -> DuplicateFilter
AttributeCreator
    ATTR_TABLE:
      SET_TO ERROR_TYPE (varchar(14)) = NULL_ATTRIBUTE
      SET_TO ERROR_DESC (varchar(37)) = One or more critical fields are empty
      SET_TO SOURCE_FC (varchar(15)) = Water_Mains_W13
    -> AttributeManager
DuplicateFilter
    INPUT_ORDERED_CHOICE_LOOKUP = NO
    KEYATTR = Waterma2
    INPUT_ORDERED_CHOICE = No
    UNIQUE -> Tester_2
    DUPLICATE -> AttributeCreator_2
Tester_2
    BOOL_OP = OR
    TEST_CLAUSE = TEST @Value(Waterma4) = 0
    TEST_MODE = TEST
    PASSED -> AttributeCreator_3
    FAILED -> Tester_3
AttributeCreator_3
    ATTR_TABLE:
      SET_TO ERROR_TYPE (varchar(16)) = INVALID_DIAMETER
      SET_TO ERROR_DESC (varchar(22)) = Diameter value is zero
      SET_TO SOURCE_FC (varchar(15)) = Water_Mains_W13
    -> AttributeManager
Tester_3
    BOOL_OP = OR
    TEST_CLAUSE:
      TEST @Value(Waterma5) = UNK
      TEST Waterma5 ATTRIBUTE_IS_EMPTY ""
    TEST_MODE = TEST
    PASSED -> AttributeCreator_4
    FAILED -> Tester_4
AttributeCreator_4
    ATTR_TABLE:
      SET_TO ERROR_TYPE (varchar(16)) = INVALID_MATERIAL
      SET_TO ERROR_DESC (varchar(28)) = Material is unknown or empty
      SET_TO SOURCE_FC (varchar(15)) = Water_Mains_W13
    -> AttributeManager
Tester_4
    BOOL_OP = OR
    TEST_CLAUSE:
      TEST @Value(Waterma7) < 1800
      TEST @Value(Waterma7) > 2026
    TEST_MODE = TEST
    PASSED -> AttributeCreator_5
    FAILED -> AttributeManager_3
AttributeManager_3
    ATTR_TABLE:
      RENAME_SET_VALUE Waterma2 > QA_ASSET_ID (varchar(80))
      SET_TO QA_STATUS (varchar(4)) = PASS
    USER_EXPOSED_ATTRIBUTES = QA_STATUS
    -> Mains_QA_Passed (writer FILEGDB_7)
Mains_QA_Passed (writer FILEGDB_7)
    attributes: OBJECTID objectid, _id1 double, QA_ASSET_ID text(80), Waterma3 text(80), Waterma4 double, Waterma5 text(80), Waterma6 text(80), Waterma7 double, Waterma8 double, Waterma9 text(80), Shape_Length double, QA_STATUS text(4)
AttributeCreator_5
    ATTR_TABLE:
      SET_TO ERROR_TYPE (varchar(12)) = INVALID_YEAR
      SET_TO ERROR_DESC (varchar(42)) = Install year outside valid range 1800-2026
      SET_TO SOURCE_FC (varchar(15)) = Water_Mains_W13
    -> AttributeManager
AttributeCreator_2
    ATTR_TABLE:
      SET_TO ERROR_TYPE (varchar(18)) = DUPLICATE_ASSET_ID
      SET_TO ERROR_DESC (varchar(31)) = Asset ID appears more than once
      SET_TO SOURCE_FC (varchar(15)) = Water_Mains_W13
    -> AttributeManager
AttributeManager
    ATTR_TABLE:
      RENAME_SET_VALUE Waterma2 > QA_ASSET_ID (varchar(80))
      REMOVE Waterma3 (varchar(80))
      REMOVE Waterma4 (real64)
      REMOVE Waterma5 (varchar(80))
      REMOVE Waterma6 (varchar(80))
      REMOVE Waterma7 (real64)
      REMOVE Waterma8 (real64)
      REMOVE Waterma9 (varchar(80))
    USER_EXPOSED_ATTRIBUTES = Waterma2,ERROR_TYPE,ERROR_DESC,SOURCE_FC
    -> Mains_QA_Errors (writer FILEGDB_5)
Mains_QA_Errors (writer FILEGDB_5)
    attributes: QA_ASSET_ID text(80), ERROR_TYPE text(14), ERROR_DESC text(37), SOURCE_FC text(15), OBJECTID objectid, _id1 double, Shape_Length double
